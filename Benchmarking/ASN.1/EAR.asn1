-- page 48 of book has a nice example
-- Use sequence whenever possible => ASN.1 complete:  "from an encoding point of view in BER (the TLVs are in textual order for SEQUENCE, in an
-- order chosen by the encoder for SET), and also from the more theoretical stand-point that "order is
-- not semantically significant" in SET."

-- ASN.1 complete: "you are designing a new protocol, use UTF8String for your character string fields unless you have a very good reason not to do so"

-- Based on the CDDL definition in https://thomas-fossati.github.io/draft-ear/draft-fv-rats-ear.html
World-Schema DEFINITIONS AUTOMATIC TAGS ::= -- tagging of SEQUENCE done automatically starting from 0
BEGIN
EAR ::= SEQUENCE {
eat-profile UTF8String ("tag:github.com,2023:veraison/ear"),
iat INTEGER,
ear-verifierID  AR4si-verifierID,
ear-rawEvidence UTF8String (PATTERN "[A-Za-z0-9_=-]+") OPTIONAL,
eat-submods SEQUENCE SIZE(1..100) OF SEQUENCE {
    attesterID UTF8String, 
    ear-appraisal  EAR-APPRAISAL
},
eat-nonce UTF8String (SIZE (10..74)) OPTIONAL
}

AR4si-verifierID ::= SEQUENCE {
  build UTF8String,
  developer UTF8String

}

EAR-APPRAISAL ::= SEQUENCE {
ear-status ENUMERATED {none(0),
                        affirming(2),
                        warning(32),
                        contraindicated(96)},
ear-trustworthinessVector AR4si-trustworthinessVector OPTIONAL,
ear-appraisalPolicyID UTF8String OPTIONAL

}

AR4si-trustworthinessVector ::= SEQUENCE  { -- Is there a way to set a non-empty constraint here?
   instance-identity [0] IMPLICIT AR4si-trustworthinessClaim OPTIONAL,
   configuration [1] IMPLICIT AR4si-trustworthinessClaim OPTIONAL,
   executables [2] IMPLICIT AR4si-trustworthinessClaim OPTIONAL,
   file-system [3] IMPLICIT AR4si-trustworthinessClaim OPTIONAL,
   hardware [4] IMPLICIT AR4si-trustworthinessClaim OPTIONAL,
   runtime-opaque [5] IMPLICIT AR4si-trustworthinessClaim OPTIONAL,
   storage-opaque [6] IMPLICIT AR4si-trustworthinessClaim OPTIONAL,
   sourced-data [7] IMPLICIT AR4si-trustworthinessClaim OPTIONAL
}

AR4si-trustworthinessClaim ::= INTEGER (-128..127)

END


-- https://www.oss.com/asn1/resources/asn1-made-simple/advanced-constraints.html
